# -*- coding: utf-8 -*-
import FreeCAD as App
import Part
import BOPTools.JoinFeatures


import Mesh



doc = App.activeDocument()

objs = doc.Objects
for obj in objs:
    name = obj.Name
    doc.removeObject(name)




import FreeCAD
import Part


doc = App.activeDocument()

###########################################################################
###########################################################################
###########################################################################
#############                                                 #############
#############         MAKING THE MKR BOARD FOR CUTTING        #############
#############                                                 #############
###########################################################################
###########################################################################
###########################################################################


MKR_HEIGHT = 1.6
MKR_LENGTH = 25 + 1
MKR_WIDTH =  67.7 + 1

mkr1310 = doc.addObject("Part::Box", "Cube")
mkr1310.Length = MKR_LENGTH
mkr1310.Width = MKR_WIDTH
mkr1310.Height = MKR_HEIGHT+3
mkr1310.Placement = App.Placement(App.Vector(-(MKR_LENGTH)/2,-(MKR_WIDTH)/2,0 ),App.Rotation(App.Vector(0,0,1),0)) 



fillet = doc.addObject("Part::Fillet","Fillet")
fillet.Base = mkr1310
__fillets__ = []
__fillets__.append((1,2.00,2.00))
__fillets__.append((3,2.00,2.00))
__fillets__.append((5,2.00,2.00))
__fillets__.append((7,2.00,2.00))
fillet.Edges = __fillets__
del __fillets__

doc.recompute()


tmpbox = App.ActiveDocument.addObject("Part::Feature","mkr1310")
tmpbox.Shape=Part.Solid(Part.Shell(fillet.Shape.Faces))

doc.removeObject('Fillet')
doc.removeObject(mkr1310.Label)

mkr1310 = tmpbox


SCREW_HEAD_DIAM = 2.4 -1

lengths = [-10.25,10.25,-10.25,10.25]
widths = [-25.40,-25.40,31.60,31.60]

for i in range(4):

	ScrewCut = doc.addObject("Part::Cylinder","ScrewCut")
	ScrewCut.Height = 10
	if i == 2:
		ScrewCut.Radius = SCREW_HEAD_DIAM/2  - 0.5
	else:
		ScrewCut.Radius = SCREW_HEAD_DIAM/2
	ScrewCut.Placement = App.Placement(App.Vector(lengths[i],widths[i] ,0),App.Rotation(App.Vector(0,1,0),0)) 
	
	
	
	
	
	cut = doc.addObject("Part::Cut","Cut")
	doc.Cut.Base = mkr1310
	doc.Cut.Tool = ScrewCut
	doc.recompute()
	
	tmpbox =doc.addObject("Part::Feature","mkr1310")

	tmpbox .Shape=Part.Solid(Part.Shell(cut.Shape.Faces))
	
	doc.removeObject(cut.Label)
	doc.removeObject(ScrewCut.Label)
	doc.removeObject(mkr1310.Label)
	doc.recompute()
	mkr1310 = tmpbox


PINS_HEIGHT = 3
PINS_LENGTH = 2
PINS_WIDTH =  36.0
pinbox1 = doc.addObject("Part::Box", "pinbox1")
pinbox1.Length = PINS_LENGTH
pinbox1.Width = PINS_WIDTH
pinbox1.Height = PINS_HEIGHT
pinbox1.Placement = App.Placement(App.Vector(9.10,-22.5,-PINS_HEIGHT+0.5 ),App.Rotation(App.Vector(0,0,1),0)) 

pinbox2 = doc.addObject("Part::Box", "pinbox2")
pinbox2.Length = PINS_LENGTH
pinbox2.Width = PINS_WIDTH
pinbox2.Height = PINS_HEIGHT
pinbox2.Placement = App.Placement(App.Vector(-11.10,-22.5,-PINS_HEIGHT+0.5 ),App.Rotation(App.Vector(0,0,1),0)) 


fusion = doc.addObject("Part::MultiFuse","Fusion")
doc.Fusion.Shapes = [doc.mkr1310,doc.pinbox1,doc.pinbox2]
doc.recompute()

mkr1310final =doc.addObject("Part::Feature","mkr1310final")

mkr1310final .Shape=Part.Solid(Part.Shell(fusion.Shape.Faces))
doc.removeObject(pinbox1.Label)
doc.removeObject(fusion.Label)

doc.removeObject(pinbox2.Label)
doc.removeObject(mkr1310.Label)


	
doc.recompute()



###########################################################################
###########################################################################
###########################################################################
#############                                                 #############
#############         MAKING THE GPS BOARD FOR CUTTING        #############
#############                                                 #############
###########################################################################
###########################################################################
###########################################################################


GPS_HEIGHT = 1.6 #+ 10
GPS_LENGTH = 25.4 #+ 1
GPS_WIDTH =  25.4 #+ 1

gps = doc.addObject("Part::Box", "Cube")
gps.Length = GPS_LENGTH
gps.Width = GPS_WIDTH
gps.Height = GPS_HEIGHT
gps.Placement = App.Placement(App.Vector(-(GPS_LENGTH)/2,-(GPS_WIDTH)/2,0 ),App.Rotation(App.Vector(0,0,1),0)) 



fillet = doc.addObject("Part::Fillet","Fillet")
fillet.Base = gps
__fillets__ = []
__fillets__.append((1,2.00,2.00))
__fillets__.append((3,2.00,2.00))
__fillets__.append((5,2.00,2.00))
__fillets__.append((7,2.00,2.00))
fillet.Edges = __fillets__
del __fillets__

doc.recompute()


tmpbox = App.ActiveDocument.addObject("Part::Feature","gpstmp")
tmpbox.Shape=Part.Solid(Part.Shell(fillet.Shape.Faces))

doc.removeObject('Fillet')
doc.removeObject(gps.Label)

gps = tmpbox


SCREW_HEAD_DIAM = 2.4 - 1.0

lengths = [-10.16,10.16,-10.16,10.16]
widths = [-10.16,-10.16,10.16,10.16]

for i in range(0):
	if i ==1: continue
	if i ==0: continue
	if i ==2: continue

	ScrewCut = doc.addObject("Part::Cylinder","ScrewCut")
	ScrewCut.Height = 20
	ScrewCut.Radius = SCREW_HEAD_DIAM/2
	ScrewCut.Placement = App.Placement(App.Vector(lengths[i],widths[i] ,0),App.Rotation(App.Vector(0,1,0),0)) 
	
	
	
	
	
	cut = doc.addObject("Part::Cut","Cut")
	doc.Cut.Base = gps
	doc.Cut.Tool = ScrewCut
	doc.recompute()
	
	tmpbox =doc.addObject("Part::Feature","gps"+str(i))

	tmpbox .Shape=Part.Solid(Part.Shell(cut.Shape.Faces))
	
	doc.removeObject(cut.Label)
	doc.removeObject(ScrewCut.Label)
	doc.removeObject(gps.Label)
	doc.recompute()
	gps = tmpbox


ScrewCut = doc.addObject("Part::Cylinder","ScrewCut")
ScrewCut.Height = 20
ScrewCut.Radius = 2.5/2
i = 3
ScrewCut.Placement = App.Placement(App.Vector(lengths[i],widths[i] ,-10),App.Rotation(App.Vector(0,1,0),0)) 



fusion = doc.addObject("Part::MultiFuse","Fusion")
doc.Fusion.Shapes = [doc.gpstmp,doc.ScrewCut]
doc.recompute()

gps =doc.addObject("Part::Feature","gps3")

gps .Shape=Part.Solid(Part.Shell(fusion.Shape.Faces))

doc.removeObject(ScrewCut.Label)
doc.removeObject("gpstmp")
doc.removeObject("Fusion")

doc.recompute()


ScrewCut = doc.addObject("Part::Cylinder","ScrewCut")
ScrewCut.Height = 20
ScrewCut.Radius = 2.6/2
i = 1
ScrewCut.Placement = App.Placement(App.Vector(lengths[i],widths[i] ,-10),App.Rotation(App.Vector(0,1,0),0)) 



fusion = doc.addObject("Part::MultiFuse","Fusion")
doc.Fusion.Shapes = [doc.gps3,doc.ScrewCut]
doc.recompute()

gps =doc.addObject("Part::Feature","gps")

gps .Shape=Part.Solid(Part.Shell(fusion.Shape.Faces))

doc.removeObject(ScrewCut.Label)
doc.removeObject("gps3")
doc.removeObject("Fusion")

doc.recompute()



###########################################################################
###########################################################################
###########################################################################
#############                                                 #############
#############         MAKING THE IMU BOARD FOR CUTTING        #############
#############                                                 #############
###########################################################################
###########################################################################
###########################################################################


IMU_HEIGHT = 1.6+1.4
IMU_LENGTH = 17.78 + 1
IMU_WIDTH =  25.4 + 1

imu = doc.addObject("Part::Box", "Cube")
imu.Length = IMU_LENGTH
imu.Width = IMU_WIDTH
imu.Height = IMU_HEIGHT
imu.Placement = App.Placement(App.Vector(-(IMU_LENGTH)/2,-(IMU_WIDTH)/2,0 ),App.Rotation(App.Vector(0,0,1),0)) 



fillet = doc.addObject("Part::Fillet","Fillet")
fillet.Base = imu
__fillets__ = []
__fillets__.append((1,2.00,2.00))
__fillets__.append((3,2.00,2.00))
__fillets__.append((5,2.00,2.00))
__fillets__.append((7,2.00,2.00))
fillet.Edges = __fillets__
del __fillets__

doc.recompute()


tmpbox = App.ActiveDocument.addObject("Part::Feature","imu")
tmpbox.Shape=Part.Solid(Part.Shell(fillet.Shape.Faces))

doc.removeObject('Fillet')
doc.removeObject(imu.Label)

imu = tmpbox


SCREW_HEAD_DIAM = 2.4 -1


lengths = [-6.35,-6.35,6.35,6.35]
widths = [-10.16,10.16,-10.16,10.16]

for i in range(4):

	if i == 0: continue
	ScrewCut = doc.addObject("Part::Cylinder","ScrewCut")
	ScrewCut.Height = 10
	ScrewCut.Radius = SCREW_HEAD_DIAM/2
	ScrewCut.Placement = App.Placement(App.Vector(lengths[i],widths[i] ,0),App.Rotation(App.Vector(0,1,0),0)) 
	
	
	
	
	
	cut = doc.addObject("Part::Cut","Cut")
	doc.Cut.Base = imu
	doc.Cut.Tool = ScrewCut
	doc.recompute()
	
	tmpbox =doc.addObject("Part::Feature","imu")

	tmpbox .Shape=Part.Solid(Part.Shell(cut.Shape.Faces))
	
	doc.removeObject(cut.Label)
	doc.removeObject(ScrewCut.Label)
	doc.removeObject(imu.Label)
	doc.recompute()
	imu = tmpbox



	
doc.recompute()

#########################END OF CHIP MAKING #######################################








########### SCREWS IN THE BASE



SCREW_HEAD_HEIGHT = 6 +3
SCREW_HEAD_DIAM = 2.5#1.8

RIDER_HOLE_WIDTH = 63
RIDER_HOLE_LENGTH = 44.5


c1 =doc.addObject("Part::Feature","c1")
c2 =doc.addObject("Part::Feature","c2")
c3 =doc.addObject("Part::Feature","c3")
c4 =doc.addObject("Part::Feature","c4")
c5 =doc.addObject("Part::Feature","c5")
objlist = [c1,c2,c3,c4,c5]
lengths = [-RIDER_HOLE_LENGTH/2,-RIDER_HOLE_LENGTH/2,RIDER_HOLE_LENGTH/2,RIDER_HOLE_LENGTH/2,RIDER_HOLE_LENGTH/2]
widths = [-RIDER_HOLE_WIDTH/2,RIDER_HOLE_WIDTH/2,-RIDER_HOLE_WIDTH/2,RIDER_HOLE_WIDTH/2,RIDER_HOLE_WIDTH/2]
for i in range(4):

	ScrewCut1 = doc.addObject("Part::Cylinder","ScrewCut1")
	ScrewCut1.Height = SCREW_HEAD_HEIGHT + 10
	ScrewCut1.Radius = SCREW_HEAD_DIAM/2
	ScrewCut1.Placement = App.Placement(App.Vector(lengths[i],widths[i] ,0),App.Rotation(App.Vector(0,1,0),0)) 
	
	
	outer = doc.addObject("Part::Cylinder","Cylinder2")
	if i == 0:
		outer.Height = SCREW_HEAD_HEIGHT + 6
	else:
		outer.Height = SCREW_HEAD_HEIGHT
	outer.Radius = SCREW_HEAD_DIAM
	outer.Placement = App.Placement(App.Vector(lengths[i],widths[i] ,0),App.Rotation(App.Vector(0,1,0),0)) 
	
	
	
	cut = doc.addObject("Part::Cut","Cut")
	doc.Cut.Base = outer
	doc.Cut.Tool = ScrewCut1
	doc.recompute()
	

	cutsolid = objlist[i]
	cutsolid .Shape=Part.Solid(Part.Shell(cut.Shape.Faces))
	
	doc.removeObject(cut.Label)
	doc.removeObject(ScrewCut1.Label)
	doc.removeObject(outer.Label)
	doc.recompute()


doc.recompute()



HOLDER_HEIGHT = 3
HOLDER_LENGTH = RIDER_HOLE_LENGTH+3.6
HOLDER_WIDTH =  RIDER_HOLE_WIDTH+3.6
chipholder = doc.addObject("Part::Box", "chipholder")
chipholder.Length = HOLDER_LENGTH
chipholder.Width = HOLDER_WIDTH
chipholder.Height = HOLDER_HEIGHT
chipholder.Placement = App.Placement(App.Vector(-(HOLDER_LENGTH)/2,-(HOLDER_WIDTH)/2,SCREW_HEAD_HEIGHT-3 ),App.Rotation(App.Vector(0,0,1),0)) 



fillet = doc.addObject("Part::Fillet","Fillet")
fillet.Base = chipholder
__fillets__ = []
__fillets__.append((1,2.00,2.00))
__fillets__.append((3,2.00,2.00))
__fillets__.append((5,2.00,2.00))
__fillets__.append((7,2.00,2.00))
fillet.Edges = __fillets__
del __fillets__

doc.recompute()


tmpbox = App.ActiveDocument.addObject("Part::Feature","tmpbox")
tmpbox.Shape=Part.Solid(Part.Shell(fillet.Shape.Faces))

doc.removeObject('Fillet')
doc.removeObject(chipholder.Label)

chipholder = tmpbox


for i in range(5):

	ScrewCut1 = doc.addObject("Part::Cylinder","ScrewCut1")
	ScrewCut1.Height = 15
	ScrewCut1.Radius = SCREW_HEAD_DIAM/2
	ScrewCut1.Placement = App.Placement(App.Vector(lengths[i],widths[i] ,0),App.Rotation(App.Vector(0,1,0),0)) 
	
	
	
	
	
	cut = doc.addObject("Part::Cut","Cut")
	doc.Cut.Base = chipholder
	doc.Cut.Tool = ScrewCut1
	doc.recompute()
	
	tmpbox =doc.addObject("Part::Feature","chipholder")

	tmpbox .Shape=Part.Solid(Part.Shell(cut.Shape.Faces))
	
	doc.removeObject(cut.Label)
	doc.removeObject(ScrewCut1.Label)
	doc.removeObject(chipholder.Label)
	doc.recompute()
	chipholder = tmpbox


JOINER_HEIGHT = SCREW_HEAD_HEIGHT - 1
JOINER_LENGTH = RIDER_HOLE_LENGTH+3.6
JOINER_WIDTH =  5.0
joinerbox = doc.addObject("Part::Box", "joinerbox")
joinerbox.Length = JOINER_LENGTH
joinerbox.Width = JOINER_WIDTH
joinerbox.Height = JOINER_HEIGHT
joinerbox.Placement = App.Placement(App.Vector(-(HOLDER_LENGTH)/2,-(RIDER_HOLE_WIDTH)/2+11,1 ),App.Rotation(App.Vector(0,0,1),0)) 



JOINER2_HEIGHT = SCREW_HEAD_HEIGHT 
JOINER2_LENGTH = 5
JOINER2_WIDTH =  25.0
joinerbox2 = doc.addObject("Part::Box", "joinerbox2")
joinerbox2.Length = JOINER2_LENGTH
joinerbox2.Width = JOINER2_WIDTH
joinerbox2.Height = JOINER2_HEIGHT
joinerbox2.Placement = App.Placement(App.Vector((HOLDER_LENGTH)/2 - JOINER2_LENGTH ,-(RIDER_HOLE_WIDTH)/2+11,0 ),App.Rotation(App.Vector(0,0,1),0)) 


### IMU STAND



IMU_HOLDER_HEIGHT = 6+2
IMU_HOLDER_LENGTH = 17
IMU_HOLDER_WIDTH =  24
imuholder = doc.addObject("Part::Box", "imuholder")
imuholder.Length = IMU_HOLDER_LENGTH
imuholder.Width = IMU_HOLDER_WIDTH
imuholder.Height = IMU_HOLDER_HEIGHT
imuholder.Placement = App.Placement(App.Vector(-24.1,-33.3,SCREW_HEAD_HEIGHT ),App.Rotation(App.Vector(0,0,1),0)) 



fillet = doc.addObject("Part::Fillet","Fillet")
fillet.Base = imuholder
__fillets__ = []
#__fillets__.append((7,2.00,2.00))
#__fillets__.append((3,2.00,2.00))
#__fillets__.append((5,2.00,2.00))
__fillets__.append((1,2.00,2.00))
fillet.Edges = __fillets__
del __fillets__

doc.recompute()



tmpbox = App.ActiveDocument.addObject("Part::Feature","tmpbox")
tmpbox.Shape=Part.Solid(Part.Shell(fillet.Shape.Faces))

doc.removeObject('Fillet')
doc.removeObject(imuholder.Label)

imuholder = tmpbox



IMU_HOLDER_HEIGHT = 6+0.5+3
IMU_HOLDER_LENGTH = 17
IMU_HOLDER_WIDTH =  24
cutimuholder = doc.addObject("Part::Box", "cutimuholder")
cutimuholder.Length = IMU_HOLDER_LENGTH
cutimuholder.Width = IMU_HOLDER_WIDTH
cutimuholder.Height = IMU_HOLDER_HEIGHT
cutimuholder.Placement = App.Placement(App.Vector(-24.1+3,-33.3+3,SCREW_HEAD_HEIGHT-0.5 ),App.Rotation(App.Vector(0,0,1),00)) 



fillet = doc.addObject("Part::Fillet","Fillet")
fillet.Base = cutimuholder
__fillets__ = []
__fillets__.append((7,2.00,2.00))
#__fillets__.append((3,2.00,2.00))
#__fillets__.append((5,2.00,2.00))
#__fillets__.append((7,2.00,2.00))
fillet.Edges = __fillets__
del __fillets__

doc.recompute()


tmpbox = App.ActiveDocument.addObject("Part::Feature","tmpbox")
tmpbox.Shape=Part.Solid(Part.Shell(fillet.Shape.Faces))

doc.removeObject('Fillet')
doc.removeObject(cutimuholder.Label)

cutimuholder = tmpbox



	
cut = doc.addObject("Part::Cut","Cut")
doc.Cut.Base = imuholder
doc.Cut.Tool = cutimuholder
doc.recompute()
	
tmpbox =doc.addObject("Part::Feature","imuholder")

tmpbox .Shape=Part.Solid(Part.Shell(cut.Shape.Faces))
	
doc.removeObject(cut.Label)
doc.removeObject(cutimuholder.Label)
doc.removeObject(imuholder.Label)
doc.recompute()
imuholder = tmpbox


ScrewCut1 = doc.addObject("Part::Cylinder","ScrewCut1")
ScrewCut1.Height = 100
ScrewCut1.Radius = SCREW_HEAD_DIAM/2
i = 0
ScrewCut1.Placement = App.Placement(App.Vector(lengths[i],widths[i] ,0),App.Rotation(App.Vector(0,1,0),0)) 
	

	
cut = doc.addObject("Part::Cut","Cut")
doc.Cut.Base = imuholder
doc.Cut.Tool = ScrewCut1
doc.recompute()
	
tmpbox =doc.addObject("Part::Feature","imuholder2")

tmpbox .Shape=Part.Solid(Part.Shell(cut.Shape.Faces))
	
doc.removeObject(cut.Label)
doc.removeObject(ScrewCut1.Label)
doc.removeObject(imuholder.Label)
doc.recompute()
imuholder = tmpbox

#imuholder.Placement = App.Placement(App.Vector(19,28.2,SCREW_HEAD_HEIGHT ),App.Rotation(App.Vector(0,0,1),0)) 






OUT_HEAD_DIAM = 2.4 -1

lengths = [-10.25,10.25,-10.25,10.25]
widths = [25.40,25.40,-31.60,-31.60]

for i in range(3):


	ScrewCut = doc.addObject("Part::Cylinder","ScrewCut"+str(i))
	ScrewCut.Height = 3

	ScrewCut.Radius = OUT_HEAD_DIAM/2
	ScrewCut.Placement = App.Placement(App.Vector(lengths[i]+12.0,widths[i]+0.10 ,8),App.Rotation(App.Vector(0,0,1),0)) 






fusion = doc.addObject("Part::MultiFuse","Fusion")
doc.Fusion.Shapes = [doc.joinerbox,doc.joinerbox2,doc.c2,doc.c4,doc.c3,doc.chipholder,doc.c1,doc.imuholder2,doc.ScrewCut0,doc.ScrewCut1,doc.ScrewCut2]
doc.recompute()

baseholder =doc.addObject("Part::Feature","baseholder")

baseholder .Shape=Part.Solid(Part.Shell(fusion.Shape.Faces))
	
	
doc.recompute()

doc.removeObject(fusion.Label)
for c in objlist: doc.removeObject(c.Label) 
doc.removeObject(chipholder.Label)
doc.removeObject(joinerbox.Label)
doc.removeObject(joinerbox2.Label)
doc.removeObject(imuholder.Label)
doc.removeObject(doc.ScrewCut0.Label)
doc.removeObject(doc.ScrewCut1.Label)
doc.removeObject(doc.ScrewCut2.Label)



	




mkr1310final.Placement = App.Placement(App.Vector(12.0,0.10,8.0 ),App.Rotation(App.Vector(0,0,1),180)) 


doc.recompute()

cut = doc.addObject("Part::Cut","Cut")
doc.Cut.Base = baseholder
doc.Cut.Tool = mkr1310final
doc.recompute()

tmpbox =doc.addObject("Part::Feature","baseholder2")

tmpbox .Shape=Part.Solid(Part.Shell(cut.Shape.Faces))

doc.removeObject(cut.Label)
doc.removeObject(baseholder.Label)
doc.recompute()
baseholder = tmpbox


gps.Placement = App.Placement(App.Vector(-13.70,12.350,9.6 ),App.Rotation(App.Vector(0,0,1),0)) 


cut = doc.addObject("Part::Cut","Cut")
doc.Cut.Base = baseholder
doc.Cut.Tool = gps
doc.recompute()

tmpbox =doc.addObject("Part::Feature","baseholder3")

tmpbox .Shape=Part.Solid(Part.Shell(cut.Shape.Faces))

doc.removeObject(cut.Label)
doc.removeObject(baseholder.Label)
doc.recompute()
baseholder = tmpbox

imu.Placement = App.Placement(App.Vector(-15.9,-21.35,14 ),App.Rotation(App.Vector(0,0,1),0)) 



cut = doc.addObject("Part::Cut","Cut")
doc.Cut.Base = baseholder
doc.Cut.Tool = imu
doc.recompute()

tmpbox =doc.addObject("Part::Feature","baseholder3")

tmpbox .Shape=Part.Solid(Part.Shell(cut.Shape.Faces))

doc.removeObject(cut.Label)
doc.removeObject(baseholder.Label)
doc.recompute()
baseholder = tmpbox


doc.removeObject(mkr1310final.Label)
doc.removeObject(gps.Label)
doc.removeObject(imu.Label)
doc.recompute()

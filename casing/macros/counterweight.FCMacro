# -*- coding: utf-8 -*-
import FreeCAD as App
import Part
import BOPTools.JoinFeatures

import sys
import Mesh


doc = App.activeDocument()

objs = doc.Objects
for obj in objs:
    name = obj.Name
    doc.removeObject(name)




BOX_HEIGHT = 80
BOX_WIDTH = 50
BOX_LENGTH = 50
BOX_WIDTH_TOP = 70

outerbox = doc.addObject("Part::Wedge", "outerbox")
outerbox.Zmin = -BOX_WIDTH/2
outerbox.Xmin = -BOX_LENGTH/2 
outerbox.Z2min = -BOX_WIDTH_TOP/2
outerbox.X2min = -BOX_LENGTH/2 
outerbox.Zmax = BOX_WIDTH/2
outerbox.Xmax = BOX_LENGTH/2
outerbox.Z2max = BOX_WIDTH_TOP/2
outerbox.X2max = BOX_LENGTH/2 

outerbox.Ymin = 0
outerbox.Ymax = BOX_HEIGHT


outerbox.Placement = App.Placement(App.Vector(0,0,0),App.Rotation(App.Vector(1,0,0),90)) 


WALL_THICKNESS = 3

INNER_BOX_YMIN = 14
INNER_BOX_YMAX = 62

INNER_BOX_LENGTH  = BOX_LENGTH - 2*WALL_THICKNESS

INNER_BOX_WIDTH = BOX_WIDTH + (BOX_WIDTH_TOP-BOX_WIDTH)*INNER_BOX_YMIN/BOX_HEIGHT - 2*WALL_THICKNESS
INNER_BOX_WIDTH_TOP = BOX_WIDTH_TOP + (BOX_WIDTH-BOX_WIDTH_TOP)*(BOX_HEIGHT-INNER_BOX_YMAX)/BOX_HEIGHT - 2*WALL_THICKNESS

innerbox = doc.addObject("Part::Wedge", "innerbox")
innerbox.Zmin = -INNER_BOX_WIDTH/2
innerbox.Xmin = -INNER_BOX_LENGTH/2 
innerbox.Z2min = -INNER_BOX_WIDTH_TOP/2
innerbox.X2min = -INNER_BOX_LENGTH/2 
innerbox.Zmax = INNER_BOX_WIDTH/2
innerbox.Xmax = INNER_BOX_LENGTH/2
innerbox.Z2max = INNER_BOX_WIDTH_TOP/2
innerbox.X2max = INNER_BOX_LENGTH/2 

innerbox.Ymin = INNER_BOX_YMIN
innerbox.Ymax = INNER_BOX_YMAX


innerbox.Placement = App.Placement(App.Vector(0,0,0),App.Rotation(App.Vector(1,0,0),90)) 




#innerbox = doc.addObject("Part::Box", "innerbox")
#innerbox.Length = INNER_BOX_LENGTH
#innerbox.Width = INNER_BOX_WIDTH
#innerbox.Height = INNER_BOX_HEIGHT
#innerbox.Placement = App.Placement(App.Vector(-INNER_BOX_LENGTH/2,-INNER_BOX_WIDTH/2,0),App.Rotation(App.Vector(0,0,1),0)) 



#MainBox = doc.addObject("Part::Box", "MainBox")
#MainBox.Length = BOX_LENGTH
#MainBox.Width = BOX_WIDTH
#MainBox.Height = BOX_HEIGHT
#MainBox.Placement = App.Placement(App.Vector(-BOX_LENGTH/2,-BOX_WIDTH/2,0),App.Rotation(App.Vector(0,0,1),0)) 

#doc.recompute()


CURVE_RADIUS = 100

topcurve = doc.addObject("Part::Cylinder","topcurve")
topcurve.Height = BOX_LENGTH
topcurve.Radius = CURVE_RADIUS
topcurve.Placement = App.Placement(App.Vector(-BOX_LENGTH/2,0,BOX_HEIGHT+CURVE_RADIUS-7),App.Rotation(App.Vector(0,1,0),90)) 

cut = doc.addObject("Part::Cut","Cut")
doc.Cut.Base = outerbox
doc.Cut.Tool = topcurve
doc.recompute()

outerbox2 =doc.addObject("Part::Feature","outerbox2")
outerbox2.Label="outerbox2"
outerbox2.Shape=Part.Solid(Part.Shell(cut.Shape.Faces))

doc.removeObject('Cut')
doc.removeObject('outerbox')
doc.removeObject('topcurve')
doc.recompute()




fillet = doc.addObject("Part::Fillet","Fillet")
fillet.Base = outerbox2
__fillets__ = []
__fillets__.append((2,5.00,5.00))
__fillets__.append((3,5.00,5.00))
__fillets__.append((10,5.00,5.00))
__fillets__.append((11,5.00,5.00))
fillet.Edges = __fillets__
del __fillets__

doc.recompute()


outerbox = App.ActiveDocument.addObject("Part::Feature","outerbox")
outerbox.Shape=Part.Solid(Part.Shell(fillet.Shape.Faces))

doc.removeObject('Fillet')
doc.removeObject('outerbox2')



#doc.recompute()

SCREW_RADIUS = 3.25
SCREW_LENGTH = 200
SCREW_OFFSET = 14 
SCREW_OFFSET2 = 13 

# top front screw hole

screw = doc.addObject("Part::Cylinder","screw")
screw.Height = SCREW_LENGTH
screw.Radius = SCREW_RADIUS
screw.Placement = App.Placement(App.Vector(SCREW_OFFSET,SCREW_LENGTH/2,BOX_HEIGHT-SCREW_OFFSET2),App.Rotation(App.Vector(1,0,0),90)) 



#SCREW_BUFFER_RADIUS = 6
#SCREW_BUFFER_LENGTH = BOX_WIDTH_TOP - 20

#screw_buffer = doc.addObject("Part::Cylinder","screw_buffer")
#screw_buffer.Height = SCREW_BUFFER_LENGTH
#screw_buffer.Radius = SCREW_BUFFER_RADIUS
#screw_buffer.Placement = App.Placement(App.Vector(SCREW_OFFSET,SCREW_BUFFER_LENGTH/2,BOX_HEIGHT-SCREW_OFFSET2),App.Rotation(App.Vector(1,0,0),90)) 


cut = doc.addObject("Part::Cut","Cut")
doc.Cut.Base = outerbox
doc.Cut.Tool = screw
doc.recompute()

outerbox2 =doc.addObject("Part::Feature","outerbox2")
outerbox2.Label="outerbox2"
outerbox2.Shape=Part.Solid(Part.Shell(cut.Shape.Faces))

doc.removeObject('Cut')
doc.removeObject('screw')
doc.removeObject('outerbox')
doc.recompute()



#cut = doc.addObject("Part::Cut","Cut")
#doc.Cut.Base = outerbox2
#doc.Cut.Tool = screw_buffer
#doc.recompute()

#outerbox =doc.addObject("Part::Feature","outerbox")
#outerbox.Label="outerbox"
#outerbox.Shape=Part.Solid(Part.Shell(cut.Shape.Faces))

#doc.removeObject('Cut')
#doc.removeObject('outerbox2')
#doc.removeObject('screw_buffer')
#doc.recompute()

# top back screw hole

screw = doc.addObject("Part::Cylinder","screw")
screw.Height = SCREW_LENGTH
screw.Radius = SCREW_RADIUS
screw.Placement = App.Placement(App.Vector(-SCREW_OFFSET,SCREW_LENGTH/2,BOX_HEIGHT-SCREW_OFFSET2),App.Rotation(App.Vector(1,0,0),90)) 



#SCREW_BUFFER_RADIUS = 6
#SCREW_BUFFER_LENGTH = BOX_WIDTH_TOP - 20

#screw_buffer = doc.addObject("Part::Cylinder","screw_buffer")
#screw_buffer.Height = SCREW_BUFFER_LENGTH
#screw_buffer.Radius = SCREW_BUFFER_RADIUS
#screw_buffer.Placement = App.Placement(App.Vector(-SCREW_OFFSET,SCREW_BUFFER_LENGTH/2,BOX_HEIGHT-SCREW_OFFSET2),App.Rotation(App.Vector(1,0,0),90)) 


cut = doc.addObject("Part::Cut","Cut")
doc.Cut.Base = outerbox2
doc.Cut.Tool = screw
doc.recompute()

outerbox =doc.addObject("Part::Feature","outerbox")
outerbox.Label="outerbox"
outerbox.Shape=Part.Solid(Part.Shell(cut.Shape.Faces))

doc.removeObject('Cut')
doc.removeObject('screw')
doc.removeObject('outerbox2')
doc.recompute()

##################BOTTOM SCREWS


SCREW_RADIUS = 3.25
SCREW_LENGTH = 200
SCREW_OFFSET = 14
SCREW_OFFSET2 = 7 

# top front screw hole

screw = doc.addObject("Part::Cylinder","screw")
screw.Height = SCREW_LENGTH
screw.Radius = SCREW_RADIUS
screw.Placement = App.Placement(App.Vector(SCREW_OFFSET,SCREW_LENGTH/2,SCREW_OFFSET2),App.Rotation(App.Vector(1,0,0),90)) 



#SCREW_BUFFER_RADIUS = 6
#SCREW_BUFFER_LENGTH = BOX_WIDTH_TOP - 20

#screw_buffer = doc.addObject("Part::Cylinder","screw_buffer")
#screw_buffer.Height = SCREW_BUFFER_LENGTH
#screw_buffer.Radius = SCREW_BUFFER_RADIUS
#screw_buffer.Placement = App.Placement(App.Vector(SCREW_OFFSET,SCREW_BUFFER_LENGTH/2,BOX_HEIGHT-SCREW_OFFSET2),App.Rotation(App.Vector(1,0,0),90)) 


cut = doc.addObject("Part::Cut","Cut")
doc.Cut.Base = outerbox
doc.Cut.Tool = screw
doc.recompute()

outerbox2 =doc.addObject("Part::Feature","outerbox2")
outerbox2.Label="outerbox2"
outerbox2.Shape=Part.Solid(Part.Shell(cut.Shape.Faces))

doc.removeObject('Cut')
doc.removeObject('screw')
doc.removeObject('outerbox')
doc.recompute()



#cut = doc.addObject("Part::Cut","Cut")
#doc.Cut.Base = outerbox2
#doc.Cut.Tool = screw_buffer
#doc.recompute()

#outerbox =doc.addObject("Part::Feature","outerbox")
#outerbox.Label="outerbox"
#outerbox.Shape=Part.Solid(Part.Shell(cut.Shape.Faces))

#doc.removeObject('Cut')
#doc.removeObject('outerbox2')
#doc.removeObject('screw_buffer')
#doc.recompute()

# top back screw hole

screw = doc.addObject("Part::Cylinder","screw")
screw.Height = SCREW_LENGTH
screw.Radius = SCREW_RADIUS
screw.Placement = App.Placement(App.Vector(-SCREW_OFFSET,SCREW_LENGTH/2,SCREW_OFFSET2),App.Rotation(App.Vector(1,0,0),90)) 



#SCREW_BUFFER_RADIUS = 6
#SCREW_BUFFER_LENGTH = BOX_WIDTH_TOP - 20

#screw_buffer = doc.addObject("Part::Cylinder","screw_buffer")
#screw_buffer.Height = SCREW_BUFFER_LENGTH
#screw_buffer.Radius = SCREW_BUFFER_RADIUS
#screw_buffer.Placement = App.Placement(App.Vector(-SCREW_OFFSET,SCREW_BUFFER_LENGTH/2,BOX_HEIGHT-SCREW_OFFSET2),App.Rotation(App.Vector(1,0,0),90)) 


cut = doc.addObject("Part::Cut","Cut")
doc.Cut.Base = outerbox2
doc.Cut.Tool = screw
doc.recompute()

outerbox =doc.addObject("Part::Feature","outerbox")
outerbox.Label="outerbox"
outerbox.Shape=Part.Solid(Part.Shell(cut.Shape.Faces))

doc.removeObject('Cut')
doc.removeObject('screw')
doc.removeObject('outerbox2')
doc.recompute()


TOLERANCE = 0.5

LID_BOX1_LENGTH = 40 + TOLERANCE
LID_BOX1_WIDTH = 40 + TOLERANCE
LID_BOX1_HEIGHT = INNER_BOX_YMIN + 2

lidbox1 = doc.addObject("Part::Box", "lidbox1")
lidbox1.Length = LID_BOX1_LENGTH
lidbox1.Width = LID_BOX1_WIDTH
lidbox1.Height = LID_BOX1_HEIGHT
lidbox1.Placement = App.Placement(App.Vector(-LID_BOX1_LENGTH/2,-LID_BOX1_WIDTH/2,0),App.Rotation(App.Vector(0,0,1),0)) 

cut = doc.addObject("Part::Cut","Cut")
doc.Cut.Base = outerbox
doc.Cut.Tool = lidbox1
doc.recompute()

outerbox2 =doc.addObject("Part::Feature","outerbox2")
outerbox2.Label="outerbox2"
outerbox2.Shape=Part.Solid(Part.Shell(cut.Shape.Faces))

doc.removeObject('Cut')
doc.removeObject('lidbox1')
doc.removeObject('outerbox')
doc.recompute()



LID_BOX2_LENGTH = 44 + TOLERANCE
LID_BOX2_WIDTH = 44 + TOLERANCE
LID_BOX2_HEIGHT = SCREW_OFFSET2 + SCREW_RADIUS + 2

lidbox2 = doc.addObject("Part::Box", "lidbox2")
lidbox2.Length = LID_BOX2_LENGTH
lidbox2.Width = LID_BOX2_WIDTH
lidbox2.Height = LID_BOX2_HEIGHT
lidbox2.Placement = App.Placement(App.Vector(-LID_BOX2_LENGTH/2,-LID_BOX2_WIDTH/2,0),App.Rotation(App.Vector(0,0,1),0)) 



cut = doc.addObject("Part::Cut","Cut")
doc.Cut.Base = outerbox2
doc.Cut.Tool = lidbox2
doc.recompute()

outerbox =doc.addObject("Part::Feature","outerbox")
outerbox.Label="outerbox"
outerbox.Shape=Part.Solid(Part.Shell(cut.Shape.Faces))

doc.removeObject('Cut')
doc.removeObject('lidbox2')
doc.removeObject('outerbox2')
doc.recompute()


cut = doc.addObject("Part::Cut","Cut")
doc.Cut.Base = outerbox
doc.Cut.Tool = innerbox
doc.recompute()

outerbox2 =doc.addObject("Part::Feature","outerbox2")
outerbox2.Label="outerbox2"
outerbox2.Shape=Part.Solid(Part.Shell(cut.Shape.Faces))

doc.removeObject('Cut')
doc.removeObject('innerbox')
doc.removeObject('outerbox')
doc.recompute()


## MAKE THE LID


LID_BOX1_LENGTH = 40 
LID_BOX1_WIDTH = 40 
LID_BOX1_HEIGHT = INNER_BOX_YMIN 

lidbox1 = doc.addObject("Part::Box", "lidbox1")
lidbox1.Length = LID_BOX1_LENGTH
lidbox1.Width = LID_BOX1_WIDTH
lidbox1.Height = LID_BOX1_HEIGHT
lidbox1.Placement = App.Placement(App.Vector(-LID_BOX1_LENGTH/2,-LID_BOX1_WIDTH/2,0),App.Rotation(App.Vector(0,0,1),0)) 


LID_BOX2_LENGTH = 44 
LID_BOX2_WIDTH = 44 
LID_BOX2_HEIGHT = SCREW_OFFSET2 + SCREW_RADIUS+2

lidbox2 = doc.addObject("Part::Box", "lidbox2")
lidbox2.Length = LID_BOX2_LENGTH
lidbox2.Width = LID_BOX2_WIDTH
lidbox2.Height = LID_BOX2_HEIGHT
lidbox2.Placement = App.Placement(App.Vector(-LID_BOX2_LENGTH/2,-LID_BOX2_WIDTH/2,0),App.Rotation(App.Vector(0,0,1),0)) 


LID_BOX3_LENGTH = BOX_LENGTH 
LID_BOX3_WIDTH = BOX_WIDTH 
LID_BOX3_HEIGHT = 3

#lidbox3 = doc.addObject("Part::Box", "lidbox3")
#lidbox3.Length = LID_BOX3_LENGTH
#lidbox3.Width = LID_BOX3_WIDTH
#lidbox3.Height = LID_BOX3_HEIGHT
#lidbox3.Placement = App.Placement(App.Vector(-LID_BOX3_LENGTH/2,-LID_BOX3_WIDTH/2,-LID_BOX3_HEIGHT),App.Rotation(App.Vector(0,0,1),0)) 





#INNER_BOX_WIDTH = BOX_WIDTH + (BOX_WIDTH_TOP-BOX_WIDTH)*INNER_BOX_YMIN/BOX_HEIGHT - 2*WALL_THICKNESS
LID_BOX3_WIDTH_TOP = BOX_WIDTH - LID_BOX3_HEIGHT*(BOX_WIDTH_TOP-BOX_WIDTH)/BOX_HEIGHT 

lidbox3 = doc.addObject("Part::Wedge", "lidbox3")
lidbox3.Zmin = -LID_BOX3_WIDTH_TOP/2
lidbox3.Xmin = -LID_BOX3_LENGTH/2 
lidbox3.Z2min = -LID_BOX3_WIDTH/2
lidbox3.X2min = -LID_BOX3_LENGTH/2 
lidbox3.Zmax = LID_BOX3_WIDTH_TOP/2
lidbox3.Xmax = LID_BOX3_LENGTH/2
lidbox3.Z2max = LID_BOX3_WIDTH/2
lidbox3.X2max = LID_BOX3_LENGTH/2 

lidbox3.Ymin = -LID_BOX3_HEIGHT
lidbox3.Ymax = 0


lidbox3.Placement = App.Placement(App.Vector(0,0,0),App.Rotation(App.Vector(1,0,0),90)) 













fusion = doc.addObject("Part::MultiFuse","Fusion")
doc.Fusion.Shapes = [lidbox1,lidbox2,lidbox3]
doc.recompute()

lidbox =doc.addObject("Part::Feature","lidbox")

lidbox .Shape=Part.Solid(Part.Shell(fusion.Shape.Faces))


doc.removeObject('Fusion')
doc.removeObject('lidbox1')
doc.removeObject('lidbox2')
doc.removeObject('lidbox3')




# top front screw hole

screw = doc.addObject("Part::Cylinder","screw")
screw.Height = SCREW_LENGTH
screw.Radius = SCREW_RADIUS
screw.Placement = App.Placement(App.Vector(SCREW_OFFSET,SCREW_LENGTH/2,SCREW_OFFSET2),App.Rotation(App.Vector(1,0,0),90)) 


cut = doc.addObject("Part::Cut","Cut")
doc.Cut.Base = lidbox
doc.Cut.Tool = screw
doc.recompute()

lidbox2 =doc.addObject("Part::Feature","lidbox2")
lidbox2.Label="lidbox2"
lidbox2.Shape=Part.Solid(Part.Shell(cut.Shape.Faces))

doc.removeObject('Cut')
doc.removeObject('screw')
doc.removeObject('lidbox')
doc.recompute()

screw = doc.addObject("Part::Cylinder","screw")
screw.Height = SCREW_LENGTH
screw.Radius = SCREW_RADIUS
screw.Placement = App.Placement(App.Vector(-SCREW_OFFSET,SCREW_LENGTH/2,SCREW_OFFSET2),App.Rotation(App.Vector(1,0,0),90)) 


cut = doc.addObject("Part::Cut","Cut")
doc.Cut.Base = lidbox2
doc.Cut.Tool = screw
doc.recompute()

lidbox =doc.addObject("Part::Feature","lidbox")
lidbox.Label="lidbox"
lidbox.Shape=Part.Solid(Part.Shell(cut.Shape.Faces))

doc.removeObject('Cut')
doc.removeObject('screw')
doc.removeObject('lidbox2')
doc.recompute()


FreeCADGui.getDocument("Unnamed").getObject("outerbox2").Transparency = 40

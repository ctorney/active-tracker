# -*- coding: utf-8 -*-
import FreeCAD as App
import Part
import BOPTools.JoinFeatures


import Mesh



MAX_HEIGHT = 30

# dimensions for plate that attaches to the collar
PLATE_THICKNESS = 10
PLATE_RADIUS = 200

GROW = 8
PLATE_WIDTH = 50
PLATE_LENGTH = 140 + GROW

LIPO_WIDTH = 60+2
LIPO_LENGTH = 40
LIPO_HEIGHT = 10 


blb = 116 +GROW # battery length bottom
bwb = 50 # battery width bottom
blt = 108 +GROW # battery length top
bwt = 63 # battery width top

PANEL_WIDTH = 70
PANEL_LENGTH = 55
PANEL_HEIGHT = 2
slb = blt # sodaq length bottom = battery length top
swb = bwt # sodaq width bottom
slt = PANEL_WIDTH + 12 # 24 +GROW
swt = PANEL_LENGTH + 8 #12 


doc = App.activeDocument()

objs = doc.Objects
for obj in objs:
    name = obj.Name
    doc.removeObject(name)


#rider = Mesh.insert(u"/home/ctorney/workspace/active-tracker/casing/rider.stl",doc.Label)
#doc.getObject("rider").Placement = App.Placement(App.Vector(-143,101,-16),App.Rotation(App.Vector(0,0,1),0))


outer = doc.addObject("Part::Cylinder","Cylinder1")
outer.Height = PLATE_WIDTH
outer.Radius = PLATE_RADIUS
outer.Placement = App.Placement(App.Vector(-PLATE_WIDTH/2,0,-PLATE_RADIUS),App.Rotation(App.Vector(0,1,0),90)) 


inner = doc.addObject("Part::Cylinder","Cylinder2")
inner.Height = PLATE_WIDTH
inner.Radius = PLATE_RADIUS-PLATE_THICKNESS
inner.Placement = App.Placement(App.Vector(-PLATE_WIDTH/2,0,-PLATE_RADIUS),App.Rotation(App.Vector(0,1,0),90)) 

cut = doc.addObject("Part::Cut","Cut")
doc.Cut.Base = outer
doc.Cut.Tool = inner
doc.recompute()

cutsolid =doc.addObject("Part::Feature","Cut_solid")
cutsolid .Label="Cut (Solid)"
cutsolid .Shape=Part.Solid(Part.Shell(cut.Shape.Faces))

doc.removeObject('Cut')
doc.removeObject('Cylinder1')
doc.removeObject('Cylinder2')
doc.recompute()

box = doc.addObject("Part::Box", "CutterBox")
box.Length = PLATE_LENGTH
box.Width = PLATE_LENGTH
box.Height = PLATE_LENGTH
box.Placement = App.Placement(App.Vector(-PLATE_LENGTH/2,-PLATE_LENGTH/2,-PLATE_LENGTH/2),App.Rotation(App.Vector(0,0,1),0)) 

doc.recompute()


common = doc.addObject("Part::MultiCommon","Common")
doc.Common.Shapes = [box,cutsolid,]
doc.recompute()

baseplate0 = doc.addObject("Part::Feature","baseplate0")
baseplate0.Label = "baseplate0"
baseplate0.Shape=Part.Solid(Part.Shell(common.Shape.Faces))

doc.removeObject('Common')
doc.removeObject('CutterBox')
doc.removeObject('Cut_solid')
doc.recompute()

fillet = doc.addObject("Part::Fillet","Fillet")
fillet.Base = baseplate0
__fillets__ = []
__fillets__.append((12,4.00,4.00))
__fillets__.append((4,4.00,4.00))
#__fillets__.append((5,5.00,5.00))
#__fillets__.append((10,5.00,5.00))
fillet.Edges = __fillets__
del __fillets__
#FreeCADGui.ActiveDocument.Common_solid.Visibility = False

doc.recompute()

baseplate1 = App.ActiveDocument.addObject("Part::Feature","baseplate1")
baseplate1.Label = "baseplate1"
baseplate1.Shape=Part.Solid(Part.Shell(fillet.Shape.Faces))

doc.removeObject('Fillet')
doc.removeObject('baseplate0')

fillet = doc.addObject("Part::Fillet","Fillet")
fillet.Base = baseplate1
__fillets__ = []
__fillets__.append((1,2.00,2.00))
__fillets__.append((4,2.00,2.00))
__fillets__.append((5,2.00,2.00))
__fillets__.append((6,2.00,2.00))
__fillets__.append((8,2.00,2.00))
__fillets__.append((9,2.00,2.00))
__fillets__.append((11,2.00,2.00))
__fillets__.append((14,2.00,2.00))
__fillets__.append((15,2.00,2.00))
__fillets__.append((16,2.00,2.00))
fillet.Edges = __fillets__
del __fillets__
#FreeCADGui.ActiveDocument.Common_solid.Visibility = False

doc.recompute()


baseplate2pre = App.ActiveDocument.addObject("Part::Feature","baseplate2pre")
baseplate2pre.Label = "baseplate2pre"
baseplate2pre.Shape=Part.Solid(Part.Shell(fillet.Shape.Faces))

doc.removeObject('Fillet')
doc.removeObject('baseplate1')


### END OF BASIC BASE PLATE



RIVET_HEAD_DIAM = 10
SIDE_OFFSET=15
FRONT_OFFSET=-2.0
ScrewCut1 = doc.addObject("Part::Cylinder","ScrewCut1")
ScrewCut1.Height = 100+MAX_HEIGHT + PLATE_THICKNESS
ScrewCut1.Radius = RIVET_HEAD_DIAM/2
ScrewCut1.Placement = App.Placement(App.Vector(-swt/2+SIDE_OFFSET,-slt/2 -FRONT_OFFSET ,-50),App.Rotation(App.Vector(0,1,0),0)) 





ScrewCut2 = doc.addObject("Part::Cylinder","ScrewCut2")
ScrewCut2.Height = 100+MAX_HEIGHT + PLATE_THICKNESS
ScrewCut2.Radius = RIVET_HEAD_DIAM/2
ScrewCut2.Placement = App.Placement(App.Vector(+swt/2-SIDE_OFFSET,-slt/2 -FRONT_OFFSET ,-50),App.Rotation(App.Vector(0,1,0),0)) 




ScrewCut3 = doc.addObject("Part::Cylinder","ScrewCut3")
ScrewCut3.Height = 100+MAX_HEIGHT + PLATE_THICKNESS
ScrewCut3.Radius = RIVET_HEAD_DIAM/2
ScrewCut3.Placement = App.Placement(App.Vector(-swt/2+SIDE_OFFSET,slt/2 +FRONT_OFFSET ,-50),App.Rotation(App.Vector(0,1,0),0)) 




ScrewCut4 = doc.addObject("Part::Cylinder","ScrewCut4")
ScrewCut4.Height = 100+MAX_HEIGHT + PLATE_THICKNESS
ScrewCut4.Radius = RIVET_HEAD_DIAM/2
ScrewCut4.Placement = App.Placement(App.Vector(+swt/2-SIDE_OFFSET,slt/2 +FRONT_OFFSET ,-50),App.Rotation(App.Vector(0,1,0),0)) 



### START OF HOLES INTO BASE

cut = doc.addObject("Part::Cut","Cut")
cut.Base = baseplate2pre
cut.Tool = ScrewCut1
doc.recompute()
baseplate2pre0 =doc.addObject("Part::Feature","baseplate2pre0")
baseplate2pre0 .Label="baseplate2pre0"
baseplate2pre0 .Shape=Part.Solid(Part.Shell(cut.Shape.Faces))

doc.removeObject(cut.Label)
doc.removeObject(baseplate2pre.Label)


cut = doc.addObject("Part::Cut","Cut")
cut.Base = baseplate2pre0
cut.Tool = ScrewCut2
doc.recompute()

baseplate2pre1 =doc.addObject("Part::Feature","baseplate2pre1")
baseplate2pre1 .Shape=Part.Solid(Part.Shell(cut.Shape.Faces))

doc.removeObject(cut.Label)
doc.removeObject(baseplate2pre0.Label)



cut = doc.addObject("Part::Cut","Cut")
cut.Base = baseplate2pre1
cut.Tool = ScrewCut3
doc.recompute()

baseplate2pre2 =doc.addObject("Part::Feature","baseplate2pre2")
baseplate2pre2 .Shape=Part.Solid(Part.Shell(cut.Shape.Faces))

doc.removeObject(cut.Label)
doc.removeObject(baseplate2pre1.Label)


cut = doc.addObject("Part::Cut","Cut")
cut.Base = baseplate2pre2
cut.Tool = ScrewCut4
doc.recompute()

baseplate2 =doc.addObject("Part::Feature","baseplate2")
baseplate2 .Shape=Part.Solid(Part.Shell(cut.Shape.Faces))

doc.removeObject(cut.Label)
doc.removeObject(baseplate2pre2.Label)

doc.removeObject(ScrewCut1.Label)
doc.removeObject(ScrewCut2.Label)
doc.removeObject(ScrewCut3.Label)
doc.removeObject(ScrewCut4.Label)

### END OF HOLES INTO BASE


## START OF BATTERY BOX

BASE_FLOOR_HEIGHT = LIPO_HEIGHT + 3 - PLATE_THICKNESS

lipobox = doc.addObject("Part::Wedge", "lipoBox")
lipobox.Zmin = -blb/2
lipobox.Xmin = -bwb/2
lipobox.Z2min = -blt/2
lipobox.X2min = -bwt/2
lipobox.Zmax = blb/2
lipobox.Xmax = bwb/2
lipobox.Z2max = blt/2
lipobox.X2max = bwt/2

lipobox.Ymin = -PLATE_THICKNESS
lipobox.Ymax = LIPO_HEIGHT + 3 - PLATE_THICKNESS  # 10 mm for lipo, 3 for tolerance and lower into the casing


lipobox.Placement = App.Placement(App.Vector(0,0,0),App.Rotation(App.Vector(1,0,0),90)) 

LipoFloor = doc.addObject("Part::Box", "LipoFloor")
LipoFloor.Length = LIPO_LENGTH+1
LipoFloor.Width = LIPO_WIDTH+1
LipoFloor.Height = 3 # THICKNESS OF BASE AT THINNEST POINT
LipoFloor.Placement = App.Placement(App.Vector(-(LIPO_LENGTH+1)/2,-(LIPO_WIDTH+1)/2,-PLATE_THICKNESS),App.Rotation(App.Vector(0,0,1),0)) 


LipoCutterBox = doc.addObject("Part::Box", "LipoCutterBox")
LipoCutterBox.Length = LIPO_LENGTH
LipoCutterBox.Width = LIPO_WIDTH
LipoCutterBox.Height = LIPO_HEIGHT
LipoCutterBox.Placement = App.Placement(App.Vector(-LIPO_LENGTH/2  ,-LIPO_WIDTH/2 - 1,3 - PLATE_THICKNESS ),App.Rotation(App.Vector(0,0,1),0)) 

doc.recompute()
cutlipobox = doc.addObject("Part::Cut","cutlipobox")
cutlipobox.Base = lipobox
cutlipobox.Tool = LipoCutterBox
doc.recompute()



lipo1 =doc.addObject("Part::Feature","lipo1")
lipo1 .Label="Lipo Box"
lipo1 .Shape=Part.Solid(Part.Shell(cutlipobox.Shape.Faces))

doc.removeObject('cutlipobox')
doc.removeObject('lipoBox')

doc.recompute()
cutlipobox = doc.addObject("Part::Cut","cutlipobox")
cutlipobox.Base = doc.baseplate2
cutlipobox.Tool = LipoCutterBox
doc.recompute()

baseplate21 =doc.addObject("Part::Feature","baseplate21")
baseplate21 .Label="baseplate21"
baseplate21 .Shape=Part.Solid(Part.Shell(cutlipobox.Shape.Faces))

doc.removeObject('cutlipobox')
doc.removeObject('baseplate2')

doc.removeObject('LipoCutterBox')





fillet = doc.addObject("Part::Fillet","Fillet")
fillet.Base = lipo1
__fillets__ = []
__fillets__.append((2,2.00,2.00))
__fillets__.append((4,2.00,2.00))
__fillets__.append((9,2.00,2.00))
__fillets__.append((16,2.00,2.00))
fillet.Edges = __fillets__
del __fillets__

doc.recompute()


lipo2 = App.ActiveDocument.addObject("Part::Feature","lipo2")
lipo2.Label = "lipo2"
lipo2.Shape=Part.Solid(Part.Shell(fillet.Shape.Faces))

doc.removeObject('Fillet')
doc.removeObject('lipo1')


j = BOPTools.JoinFeatures.makeConnect(name = 'LipoFloorJoin')
j.Objects = [doc.lipo2, doc.LipoFloor]
j.Proxy.execute(j)
j.purgeTouched()
for obj in j.ViewObject.Proxy.claimChildren():
    obj.ViewObject.hide()

lipocase=doc.addObject("Part::Feature","lipocase")
lipocase.Label="lipocase"
lipocase.Shape=Part.Solid(Part.Shell(doc.LipoFloorJoin.Shape.Faces))

doc.removeObject("LipoFloorJoin")
doc.removeObject("LipoFloor")
doc.removeObject("lipo2")
doc.recompute()


j = BOPTools.JoinFeatures.makeEmbed(name = 'BaseEmbed')
j.Base = lipocase
j.Tool = doc.baseplate21
j.Proxy.execute(j)
j.purgeTouched()
for obj in j.ViewObject.Proxy.claimChildren():
    obj.ViewObject.hide()



FullBase0=App.ActiveDocument.addObject("Part::Feature","FullBase0")
FullBase0.Label="Embed (Solid)"
FullBase0.Shape=Part.Solid(Part.Shell(doc.BaseEmbed.Shape.Faces))



doc.removeObject("BaseEmbed")
doc.removeObject("lipocase")
doc.removeObject("baseplate21")
#App.getDocument("Unnamed").recompute()
FullBase=App.ActiveDocument.addObject("Part::Feature","FullBase")

FullBase.Shape=doc.FullBase0.Shape.removeSplitter()

#App.ActiveDocument.ActiveObject.Label=App.ActiveDocument.Embed_solid.Label
#Gui.ActiveDocument.Embed_solid.hide()

#Gui.ActiveDocument.ActiveObject.ShapeColor=Gui.ActiveDocument.Embed_solid.ShapeColor
#Gui.ActiveDocument.ActiveObject.LineColor=Gui.ActiveDocument.Embed_solid.LineColor
#Gui.ActiveDocument.ActiveObject.PointColor=Gui.ActiveDocument.Embed_solid.PointColor
doc.recompute()
doc.removeObject("FullBase0")
doc.recompute()


# Macro End: /home/ctorney/workspace/active-tracker/casing/macros/merge2.FCMacro +++++++++++++++++++++++++++++++++++++++++++++++++




### START OF SODAQ ENCLOSURE


sodaqbox = doc.addObject("Part::Wedge", "sodaqbox")
sodaqbox.Zmin = -slb/2
sodaqbox.Xmin = -swb/2
sodaqbox.Z2min = -slt/2
sodaqbox.X2min = -swt/2
sodaqbox.Zmax = slb/2
sodaqbox.Xmax = swb/2
sodaqbox.Z2max = slt/2
sodaqbox.X2max = swt/2

sodaqbox.Ymin = LIPO_HEIGHT + 3 - PLATE_THICKNESS 
sodaqbox.Ymax = MAX_HEIGHT




#lipobox.Length = 50
#lipobox.Width = 80
#lipobox.Height = 20
sodaqbox.Placement = App.Placement(App.Vector(0,0,0),App.Rotation(App.Vector(1,0,0),90)) 


PanelCutterBox = doc.addObject("Part::Box", "PanelCutterBox")
PanelCutterBox.Length = PANEL_LENGTH+2
PanelCutterBox.Width = PANEL_WIDTH+2
PanelCutterBox.Height = PANEL_HEIGHT+1
PanelCutterBox.Placement = App.Placement(App.Vector(-(PANEL_LENGTH+2)/2,-(PANEL_WIDTH+2)/2,MAX_HEIGHT-PANEL_HEIGHT-1),App.Rotation(App.Vector(0,0,1),0)) 

doc.recompute()
cutpanelbox = doc.addObject("Part::Cut","cutpanelbox")
cutpanelbox.Base = sodaqbox
cutpanelbox.Tool = PanelCutterBox
doc.recompute()


sodaqbox1 =doc.addObject("Part::Feature","sodaqbox1")
sodaqbox1 .Label="sodaqbox1"
sodaqbox1 .Shape=Part.Solid(Part.Shell(cutpanelbox.Shape.Faces))

doc.removeObject('cutpanelbox')
doc.removeObject('PanelCutterBox')
doc.removeObject('sodaqbox')


CHIP_WIDTH = 82
CHIP_LENGTH = 52
CHIP_HEIGHT = 22 # MAX_HEIGHT-6-PANEL_HEIGHT-1 -3 #7-PANEL_HEIGHT

#ChipCutterBox1 = doc.addObject("Part::Box", "ChipCutterBox1")
#ChipCutterBox1.Length = CHIP_LENGTH+2+3 - 2
#ChipCutterBox1.Width = CHIP_WIDTH+2+3
#ChipCutterBox1.Height = CHIP_HEIGHT#+1
#ChipCutterBox1.Placement = App.Placement(App.Vector(-(CHIP_LENGTH+3)/2,-(CHIP_WIDTH+5)/2,LIPO_HEIGHT + 3 - PLATE_THICKNESS ),App.Rotation(App.Vector(0,0,1),0)) 

ChipCutterBox1 = doc.addObject("Part::Wedge", "ChipCutterBox1")
ChipCutterBox1.Xmin = -(CHIP_LENGTH+3)/2
ChipCutterBox1.X2min = -(CHIP_LENGTH+3)/2
ChipCutterBox1.Xmax = (CHIP_LENGTH+3)/2
ChipCutterBox1.X2max = (CHIP_LENGTH+3)/2

ChipCutterBox1.Zmin = -(CHIP_WIDTH+5)/2
ChipCutterBox1.Z2min = -(CHIP_WIDTH+2)/2
ChipCutterBox1.Zmax = (CHIP_WIDTH+5)/2
ChipCutterBox1.Z2max = (CHIP_WIDTH+2)/2

ChipCutterBox1.Ymin = LIPO_HEIGHT + 3 - PLATE_THICKNESS 
ChipCutterBox1.Ymax = CHIP_HEIGHT + LIPO_HEIGHT + 3 - PLATE_THICKNESS 
ChipCutterBox1.Placement = App.Placement(App.Vector(0,0,0),App.Rotation(App.Vector(1,0,0),90)) 



fillet = doc.addObject("Part::Fillet","Fillet")
fillet.Base = ChipCutterBox1
__fillets__ = []
__fillets__.append((2,2.00,2.00))
__fillets__.append((3,2.00,2.00))
__fillets__.append((4,2.00,2.00))
__fillets__.append((6,2.00,2.00))
__fillets__.append((7,2.00,2.00))
__fillets__.append((8,2.00,2.00))
__fillets__.append((11,2.00,2.00))
__fillets__.append((12,2.00,2.00))
fillet.Edges = __fillets__
del __fillets__

doc.recompute()


ChipCutterBox = App.ActiveDocument.addObject("Part::Feature","ChipCutterBox")
ChipCutterBox.Label = "ChipCutterBox"
ChipCutterBox.Shape=Part.Solid(Part.Shell(fillet.Shape.Faces))#

doc.removeObject('Fillet')
doc.removeObject('ChipCutterBox1')




cutchipbox = doc.addObject("Part::Cut","cutchipbox")
cutchipbox.Base = sodaqbox1
cutchipbox.Tool = ChipCutterBox
doc.recompute()


sodaqbox2 =doc.addObject("Part::Feature","sodaqbox2")
sodaqbox2 .Label="sodaqbox2"
sodaqbox2 .Shape=Part.Solid(Part.Shell(cutchipbox.Shape.Faces))

doc.removeObject('cutchipbox')
#doc.removeObject('ChipCutterBox')
doc.removeObject('sodaqbox1')



fillet = doc.addObject("Part::Fillet","Fillet")
fillet.Base = sodaqbox2
__fillets__ = []
__fillets__.append((2,2.00,2.00))
__fillets__.append((3,2.00,2.00))
__fillets__.append((4,2.00,2.00))
__fillets__.append((16,2.00,2.00))
__fillets__.append((17,2.00,2.00))
__fillets__.append((18,2.00,2.00))
__fillets__.append((19,2.00,2.00))
__fillets__.append((24,2.00,2.00))
fillet.Edges = __fillets__
del __fillets__

doc.recompute()


sodaqbox3 = App.ActiveDocument.addObject("Part::Feature","sodaqbox3")
sodaqbox3.Label = "sodaqbox3"
sodaqbox3.Shape=Part.Solid(Part.Shell(fillet.Shape.Faces))

doc.removeObject('Fillet')
doc.removeObject('sodaqbox2')


doc.recompute()


## create screws for top box

M4_THREAD_DIAM = 3.6


ScrewCut1 = doc.addObject("Part::Cylinder","ScrewCut1")
ScrewCut1.Height = 100+MAX_HEIGHT + PLATE_THICKNESS
ScrewCut1.Radius = M4_THREAD_DIAM/2
ScrewCut1.Placement = App.Placement(App.Vector(-swt/2+SIDE_OFFSET,-slt/2 - 12 -FRONT_OFFSET ,-50),App.Rotation(App.Vector(1,0,0),-10)) 



M4_THREAD_DIAM = 3.6


ScrewCut2 = doc.addObject("Part::Cylinder","ScrewCut2")
ScrewCut2.Height = 100+MAX_HEIGHT + PLATE_THICKNESS
ScrewCut2.Radius = M4_THREAD_DIAM/2
ScrewCut2.Placement = App.Placement(App.Vector(+swt/2-SIDE_OFFSET,-slt/2 -FRONT_OFFSET ,-50),App.Rotation(App.Vector(0,1,0),0)) 


M4_THREAD_DIAM = 3.6


ScrewCut3 = doc.addObject("Part::Cylinder","ScrewCut3")
ScrewCut3.Height = 100+MAX_HEIGHT + PLATE_THICKNESS
ScrewCut3.Radius = M4_THREAD_DIAM/2
ScrewCut3.Placement = App.Placement(App.Vector(-swt/2+SIDE_OFFSET,slt/2 +FRONT_OFFSET ,-50),App.Rotation(App.Vector(0,1,0),0)) 



M4_THREAD_DIAM = 3.6


ScrewCut4 = doc.addObject("Part::Cylinder","ScrewCut4")
ScrewCut4.Height = 100+MAX_HEIGHT + PLATE_THICKNESS
ScrewCut4.Radius = M4_THREAD_DIAM/2
ScrewCut4.Placement = App.Placement(App.Vector(+swt/2-SIDE_OFFSET,slt/2 +FRONT_OFFSET ,-50),App.Rotation(App.Vector(0,1,0),0)) 



### START OF SCREWS INTO SODAQ BASE

cut = doc.addObject("Part::Cut","Cut")
cut.Base = sodaqbox3
cut.Tool = ScrewCut1
doc.recompute()
sodaqbox4 =doc.addObject("Part::Feature","sodaqbox4")
sodaqbox4 .Label="sodaqbox4"
sodaqbox4 .Shape=Part.Solid(Part.Shell(cut.Shape.Faces))

doc.removeObject(cut.Label)
doc.removeObject(sodaqbox3.Label)


cut = doc.addObject("Part::Cut","Cut")
cut.Base = sodaqbox4
cut.Tool = ScrewCut2
doc.recompute()

sodaqbox5 =doc.addObject("Part::Feature","sodaqbox")
sodaqbox5 .Shape=Part.Solid(Part.Shell(cut.Shape.Faces))

doc.removeObject(cut.Label)
doc.removeObject(sodaqbox4.Label)



cut = doc.addObject("Part::Cut","Cut")
cut.Base = sodaqbox5
cut.Tool = ScrewCut3
doc.recompute()

sodaqbox6 =doc.addObject("Part::Feature","sodaqbox")
sodaqbox6 .Shape=Part.Solid(Part.Shell(cut.Shape.Faces))

doc.removeObject(cut.Label)
doc.removeObject(sodaqbox5.Label)


cut = doc.addObject("Part::Cut","Cut")
cut.Base = sodaqbox6
cut.Tool = ScrewCut4
doc.recompute()

sodaqbox7 =doc.addObject("Part::Feature","sodaqbox")
sodaqbox7 .Shape=Part.Solid(Part.Shell(cut.Shape.Faces))

doc.removeObject(cut.Label)
doc.removeObject(sodaqbox6.Label)


doc.removeObject(ScrewCut1.Label)
doc.removeObject(ScrewCut2.Label)
doc.removeObject(ScrewCut3.Label)
doc.removeObject(ScrewCut4.Label)


### END OF SCREWS INTO SODAQ CASE


# build screws for lipo box



HEX_NUT_DIAM = 7.0


ScrewCut1 = doc.addObject("Part::Prism","ScrewCut1")
ScrewCut1.Height = 100+MAX_HEIGHT + PLATE_THICKNESS
ScrewCut1.Circumradius = HEX_NUT_DIAM/2
ScrewCut1.Placement = App.Placement(App.Vector(-swt/2+SIDE_OFFSET,-slt/2 -FRONT_OFFSET ,-50),App.Rotation(App.Vector(0,1,0),0)) 





ScrewCut2 = doc.addObject("Part::Prism","ScrewCut2")
ScrewCut2.Height = 100+MAX_HEIGHT + PLATE_THICKNESS
ScrewCut2.Circumradius = HEX_NUT_DIAM/2
ScrewCut2.Placement = App.Placement(App.Vector(+swt/2-SIDE_OFFSET,-slt/2 -FRONT_OFFSET ,-50),App.Rotation(App.Vector(0,1,0),0)) 




ScrewCut3 = doc.addObject("Part::Prism","ScrewCut3")
ScrewCut3.Height = 100+MAX_HEIGHT + PLATE_THICKNESS
ScrewCut3.Circumradius = HEX_NUT_DIAM/2
ScrewCut3.Placement = App.Placement(App.Vector(-swt/2+SIDE_OFFSET,slt/2 +FRONT_OFFSET ,-50),App.Rotation(App.Vector(0,1,0),0)) 





ScrewCut4 = doc.addObject("Part::Prism","ScrewCut4")
ScrewCut4.Height = 100+MAX_HEIGHT + PLATE_THICKNESS
ScrewCut4.Circumradius = HEX_NUT_DIAM/2
ScrewCut4.Placement = App.Placement(App.Vector(+swt/2-SIDE_OFFSET,slt/2 +FRONT_OFFSET ,-50),App.Rotation(App.Vector(0,1,0),0)) 







### START OF SCREWS INTO LIPO BASE

cut = doc.addObject("Part::Cut","Cut")
cut.Base = FullBase
cut.Tool = ScrewCut1
doc.recompute()
FullBase0 =doc.addObject("Part::Feature","FullBase0")
FullBase0 .Shape=Part.Solid(Part.Shell(cut.Shape.Faces))

doc.removeObject(cut.Label)
doc.removeObject(FullBase.Label)
doc.recompute()

# screw 2
cut = doc.addObject("Part::Cut","Cut")
cut.Base = FullBase0
cut.Tool = ScrewCut2
doc.recompute()

FullBase1 =doc.addObject("Part::Feature","FullBase1")
FullBase1 .Shape=Part.Solid(Part.Shell(cut.Shape.Faces))
doc.recompute()

doc.removeObject(cut.Label)
doc.removeObject(FullBase0.Label)
doc.recompute()

# screw 2

cut = doc.addObject("Part::Cut","Cut")
cut.Base = FullBase1
cut.Tool = ScrewCut3
doc.recompute()

FullBase2 =doc.addObject("Part::Feature","FullBase2")
FullBase2 .Shape=Part.Solid(Part.Shell(cut.Shape.Faces))

doc.removeObject(cut.Label)
doc.removeObject(FullBase1.Label)
doc.recompute()


cut = doc.addObject("Part::Cut","Cut")
cut.Base = FullBase2
cut.Tool = ScrewCut4
doc.recompute()

FullBase3 =doc.addObject("Part::Feature","FullBase3")
FullBase3 .Shape=Part.Solid(Part.Shell(cut.Shape.Faces))

doc.removeObject(cut.Label)
doc.removeObject(FullBase2.Label)
doc.recompute()

doc.removeObject(ScrewCut1.Label)
doc.removeObject(ScrewCut2.Label)
doc.removeObject(ScrewCut3.Label)
doc.removeObject(ScrewCut4.Label)


### SCREWS FOR SODAQ CASE


SCREW_HEAD_HEIGHT = 4
SCREW_HEAD_DIAM = 7




ScrewCut1 = doc.addObject("Part::Cylinder","ScrewCut1")
ScrewCut1.Height = SCREW_HEAD_HEIGHT
ScrewCut1.Radius = SCREW_HEAD_DIAM/2
ScrewCut1.Placement = App.Placement(App.Vector(-swt/2+SIDE_OFFSET,-slt/2 -FRONT_OFFSET ,MAX_HEIGHT-SCREW_HEAD_HEIGHT),App.Rotation(App.Vector(0,1,0),0)) 






ScrewCut2 = doc.addObject("Part::Cylinder","ScrewCut2")
ScrewCut2.Height = SCREW_HEAD_HEIGHT
ScrewCut2.Radius = SCREW_HEAD_DIAM/2
ScrewCut2.Placement = App.Placement(App.Vector(+swt/2-SIDE_OFFSET,-slt/2 -FRONT_OFFSET ,MAX_HEIGHT-SCREW_HEAD_HEIGHT),App.Rotation(App.Vector(0,1,0),0)) 





ScrewCut3 = doc.addObject("Part::Cylinder","ScrewCut3")
ScrewCut3.Height = SCREW_HEAD_HEIGHT
ScrewCut3.Radius = SCREW_HEAD_DIAM/2
ScrewCut3.Placement = App.Placement(App.Vector(-swt/2+SIDE_OFFSET,slt/2 +FRONT_OFFSET ,MAX_HEIGHT-SCREW_HEAD_HEIGHT),App.Rotation(App.Vector(0,1,0),0)) 






ScrewCut4 = doc.addObject("Part::Cylinder","ScrewCut4")
ScrewCut4.Height = SCREW_HEAD_HEIGHT
ScrewCut4.Radius = SCREW_HEAD_DIAM/2
ScrewCut4.Placement = App.Placement(App.Vector(+swt/2-SIDE_OFFSET,slt/2 +FRONT_OFFSET ,MAX_HEIGHT-SCREW_HEAD_HEIGHT),App.Rotation(App.Vector(0,1,0),0)) 


### START OF SCREW HEADS INTO SODAQ CASE

cut = doc.addObject("Part::Cut","Cut")
cut.Base = sodaqbox7
cut.Tool = ScrewCut1
doc.recompute()
sodaqbox8 =doc.addObject("Part::Feature","sodaqbox8")
sodaqbox8 .Label="sodaqbox8"
sodaqbox8 .Shape=Part.Solid(Part.Shell(cut.Shape.Faces))

doc.removeObject(cut.Label)
doc.removeObject(sodaqbox7.Label)


cut = doc.addObject("Part::Cut","Cut")
cut.Base = sodaqbox8
cut.Tool = ScrewCut2
doc.recompute()

sodaqbox9 =doc.addObject("Part::Feature","sodaqbox9")
sodaqbox9 .Shape=Part.Solid(Part.Shell(cut.Shape.Faces))

doc.removeObject(cut.Label)
doc.removeObject(sodaqbox8.Label)



cut = doc.addObject("Part::Cut","Cut")
cut.Base = sodaqbox9
cut.Tool = ScrewCut3
doc.recompute()

sodaqbox0 =doc.addObject("Part::Feature","sodaqbox0")
sodaqbox0 .Shape=Part.Solid(Part.Shell(cut.Shape.Faces))

doc.removeObject(cut.Label)
doc.removeObject(sodaqbox9.Label)


cut = doc.addObject("Part::Cut","Cut")
cut.Base = sodaqbox0
cut.Tool = ScrewCut4
doc.recompute()

sodaqbox1 =doc.addObject("Part::Feature","sodaqbox1")
sodaqbox1 .Shape=Part.Solid(Part.Shell(cut.Shape.Faces))

doc.removeObject(cut.Label)
doc.removeObject(sodaqbox0.Label)

doc.removeObject(ScrewCut1.Label)
doc.removeObject(ScrewCut2.Label)
doc.removeObject(ScrewCut3.Label)
doc.removeObject(ScrewCut4.Label)


### END OF SCREWS INTO SODAQ CASE


CHIPBOX_MIN = LIPO_HEIGHT + 3 - PLATE_THICKNESS 


SEAL_HEIGHT = 2
SEAL_LENGTH = CHIP_LENGTH+3
SEAL_WIDTH =  CHIP_WIDTH+2+3
SealBox1 = doc.addObject("Part::Box", "SealBox1")
SealBox1.Length = SEAL_LENGTH
SealBox1.Width = SEAL_WIDTH
SealBox1.Height = SEAL_HEIGHT +1
SealBox1.Placement = App.Placement(App.Vector(-(SEAL_LENGTH)/2,-(SEAL_WIDTH)/2,CHIPBOX_MIN- SEAL_HEIGHT ),App.Rotation(App.Vector(0,0,1),0)) 


fillet = doc.addObject("Part::Fillet","Fillet")
fillet.Base = SealBox1
__fillets__ = []
__fillets__.append((1,2.00,2.00))
__fillets__.append((3,2.00,2.00))
__fillets__.append((5,2.00,2.00))
__fillets__.append((7,2.00,2.00))
fillet.Edges = __fillets__
del __fillets__

doc.recompute()


SealBox1a = App.ActiveDocument.addObject("Part::Feature","SealBox1a")
SealBox1a.Shape=Part.Solid(Part.Shell(fillet.Shape.Faces))

doc.removeObject('Fillet')
doc.removeObject('SealBox1')


doc.recompute()


SEAL_HEIGHT = 2
SEAL_LENGTH = CHIP_LENGTH+3+2.5
SEAL_WIDTH =  CHIP_WIDTH+2+3+2.5
SealBox2 = doc.addObject("Part::Box", "SealBox2")
SealBox2.Length = SEAL_LENGTH
SealBox2.Width = SEAL_WIDTH
SealBox2.Height = SEAL_HEIGHT+1
SealBox2.Placement = App.Placement(App.Vector(-(SEAL_LENGTH)/2,-(SEAL_WIDTH)/2,CHIPBOX_MIN- SEAL_HEIGHT ),App.Rotation(App.Vector(0,0,1),0)) 


fillet = doc.addObject("Part::Fillet","Fillet")
fillet.Base = SealBox2
__fillets__ = []
__fillets__.append((1,2.00,2.00))
__fillets__.append((3,2.00,2.00))
__fillets__.append((5,2.00,2.00))
__fillets__.append((7,2.00,2.00))
fillet.Edges = __fillets__
del __fillets__

doc.recompute()


SealBox2a = App.ActiveDocument.addObject("Part::Feature","SealBox2a")
SealBox2a.Shape=Part.Solid(Part.Shell(fillet.Shape.Faces))

doc.removeObject('Fillet')
doc.removeObject('SealBox2')


doc.recompute()


sealboxcut = doc.addObject("Part::Cut","sealboxcut")
sealboxcut.Base = SealBox2a
sealboxcut.Tool = SealBox1a
doc.recompute()



sealbox =doc.addObject("Part::Feature","sealbox")
sealbox.Label="sealbox"
sealbox.Shape=Part.Solid(Part.Shell(sealboxcut.Shape.Faces))

doc.removeObject('sealboxcut')
doc.recompute()

doc.removeObject('SealBox1a')
doc.removeObject('SealBox2a')

## OPENING FOR SEAL 


CHIPBOX_MIN = LIPO_HEIGHT + 3 - PLATE_THICKNESS 


INPUT_HEIGHT = 3.0
INPUT_LENGTH = CHIP_LENGTH+3 -0.25
INPUT_WIDTH =  CHIP_WIDTH+2+3 -0.25
InputBox1 = doc.addObject("Part::Box", "InputBox1")
InputBox1.Length = INPUT_LENGTH
InputBox1.Width = INPUT_WIDTH
InputBox1.Height = INPUT_HEIGHT
InputBox1.Placement = App.Placement(App.Vector(-(INPUT_LENGTH)/2,-(INPUT_WIDTH)/2,CHIPBOX_MIN- INPUT_HEIGHT ),App.Rotation(App.Vector(0,0,1),0)) 


fillet = doc.addObject("Part::Fillet","Fillet")
fillet.Base = InputBox1
__fillets__ = []
__fillets__.append((1,2.00,2.00))
__fillets__.append((3,2.00,2.00))
__fillets__.append((5,2.00,2.00))
__fillets__.append((7,2.00,2.00))
fillet.Edges = __fillets__
del __fillets__

doc.recompute()


InputBox1a = App.ActiveDocument.addObject("Part::Feature","InputBox1a")
InputBox1a.Shape=Part.Solid(Part.Shell(fillet.Shape.Faces))

doc.removeObject('Fillet')
doc.removeObject('InputBox1')


doc.recompute()


INPUT_HEIGHT = 3.0
INPUT_LENGTH = CHIP_LENGTH+3+2.5 +0.25
INPUT_WIDTH =  CHIP_WIDTH+2+3+2.5 +0.25
InputBox2 = doc.addObject("Part::Box", "InputBox2")
InputBox2.Length = INPUT_LENGTH
InputBox2.Width = INPUT_WIDTH
InputBox2.Height = INPUT_HEIGHT
InputBox2.Placement = App.Placement(App.Vector(-(INPUT_LENGTH)/2,-(INPUT_WIDTH)/2,CHIPBOX_MIN- INPUT_HEIGHT ),App.Rotation(App.Vector(0,0,1),0)) 


fillet = doc.addObject("Part::Fillet","Fillet")
fillet.Base = InputBox2
__fillets__ = []
__fillets__.append((1,2.00,2.00))
__fillets__.append((3,2.00,2.00))
__fillets__.append((5,2.00,2.00))
__fillets__.append((7,2.00,2.00))
fillet.Edges = __fillets__
del __fillets__

doc.recompute()


InputBox2a = App.ActiveDocument.addObject("Part::Feature","InputBox2a")
InputBox2a.Shape=Part.Solid(Part.Shell(fillet.Shape.Faces))

doc.removeObject('Fillet')
doc.removeObject('InputBox2')


doc.recompute()


inputboxcut = doc.addObject("Part::Cut","inputboxcut")
inputboxcut.Base = InputBox2a
inputboxcut.Tool = InputBox1a
doc.recompute()



inputbox =doc.addObject("Part::Feature","inputbox")
inputbox.Label="inputbox"
inputbox.Shape=Part.Solid(Part.Shell(inputboxcut.Shape.Faces))

doc.removeObject('inputboxcut')
doc.recompute()

doc.removeObject('InputBox1a')
doc.removeObject('InputBox2a')


##### cut out the hole


basecut = doc.addObject("Part::Cut","basecut")
basecut.Base = FullBase3
basecut.Tool = inputbox
doc.recompute()



FullBase =doc.addObject("Part::Feature","FullBase")
FullBase.Shape=Part.Solid(Part.Shell(basecut.Shape.Faces))
doc.recompute()

doc.removeObject('basecut')
doc.recompute()

doc.removeObject('inputbox')
doc.removeObject('FullBase3')

# stick seal and top together



j = BOPTools.JoinFeatures.makeConnect(name = 'TopJoin')
j.Objects = [sodaqbox1, sealbox]
j.Proxy.execute(j)
j.purgeTouched()

topcase=doc.addObject("Part::Feature","topcase")
topcase.Shape=Part.Solid(Part.Shell(doc.TopJoin.Shape.Faces))



########### SCREWS IN THE BASE



SCREW_HEAD_HEIGHT = 4
SCREW_HEAD_DIAM = 1.8

RIDER_HOLE_WIDTH = 63
RIDER_HOLE_LENGTH = 44.5



ScrewCut1 = doc.addObject("Part::Cylinder","ScrewCut1")
ScrewCut1.Height = SCREW_HEAD_HEIGHT
ScrewCut1.Radius = SCREW_HEAD_DIAM/2
ScrewCut1.Placement = App.Placement(App.Vector(-RIDER_HOLE_LENGTH/2,-RIDER_HOLE_WIDTH/2 ,BASE_FLOOR_HEIGHT-SCREW_HEAD_HEIGHT),App.Rotation(App.Vector(0,1,0),0)) 






ScrewCut2 = doc.addObject("Part::Cylinder","ScrewCut2")
ScrewCut2.Height = SCREW_HEAD_HEIGHT
ScrewCut2.Radius = SCREW_HEAD_DIAM/2
ScrewCut2.Placement = App.Placement(App.Vector(-RIDER_HOLE_LENGTH/2,RIDER_HOLE_WIDTH/2 ,BASE_FLOOR_HEIGHT-SCREW_HEAD_HEIGHT),App.Rotation(App.Vector(0,1,0),0)) 





ScrewCut3 = doc.addObject("Part::Cylinder","ScrewCut3")
ScrewCut3.Height = SCREW_HEAD_HEIGHT
ScrewCut3.Radius = SCREW_HEAD_DIAM/2
ScrewCut3.Placement = App.Placement(App.Vector(RIDER_HOLE_LENGTH/2,-RIDER_HOLE_WIDTH/2,BASE_FLOOR_HEIGHT-SCREW_HEAD_HEIGHT),App.Rotation(App.Vector(0,1,0),0)) 






ScrewCut4 = doc.addObject("Part::Cylinder","ScrewCut4")
ScrewCut4.Height = SCREW_HEAD_HEIGHT
ScrewCut4.Radius = SCREW_HEAD_DIAM/2
ScrewCut4.Placement = App.Placement(App.Vector(RIDER_HOLE_LENGTH/2,RIDER_HOLE_WIDTH/2,BASE_FLOOR_HEIGHT-SCREW_HEAD_HEIGHT),App.Rotation(App.Vector(0,1,0),0)) 



cut = doc.addObject("Part::Cut","Cut")
cut.Base = FullBase
cut.Tool = ScrewCut1
doc.recompute()
FullBase1 =doc.addObject("Part::Feature","FullBase1")
FullBase1 .Label="FullBase1"
FullBase1 .Shape=Part.Solid(Part.Shell(cut.Shape.Faces))

doc.removeObject(cut.Label)
doc.removeObject(FullBase.Label)


cut = doc.addObject("Part::Cut","Cut")
cut.Base = FullBase1
cut.Tool = ScrewCut2
doc.recompute()

FullBase =doc.addObject("Part::Feature","FullBase")
FullBase .Shape=Part.Solid(Part.Shell(cut.Shape.Faces))

doc.removeObject(cut.Label)
doc.removeObject(FullBase1.Label)



cut = doc.addObject("Part::Cut","Cut")
cut.Base = FullBase
cut.Tool = ScrewCut3
doc.recompute()

FullBase1 =doc.addObject("Part::Feature","FullBase1")
FullBase1 .Shape=Part.Solid(Part.Shell(cut.Shape.Faces))

doc.removeObject(cut.Label)
doc.removeObject(FullBase.Label)


cut = doc.addObject("Part::Cut","Cut")
cut.Base = FullBase1
cut.Tool = ScrewCut4
doc.recompute()

FullBase =doc.addObject("Part::Feature","FullBase")
FullBase .Shape=Part.Solid(Part.Shell(cut.Shape.Faces))

doc.removeObject(cut.Label)
doc.removeObject(FullBase1.Label)

doc.removeObject(ScrewCut1.Label)
doc.removeObject(ScrewCut2.Label)
doc.removeObject(ScrewCut3.Label)
doc.removeObject(ScrewCut4.Label)




ellipse = doc.addObject("Part::Ellipsoid","Ellipsoid")
doc.Ellipsoid.Radius1=20.00
doc.Ellipsoid.Radius2=10.00
doc.Ellipsoid.Radius3=25.00
doc.Ellipsoid.Angle1=-90.00
doc.Ellipsoid.Angle2=90.00
doc.Ellipsoid.Angle3=360.00
doc.Ellipsoid.Placement=App.Placement(App.Vector(0.00,0.00,MAX_HEIGHT),App.Rotation(0.00,0.00,0.00,1.00))
doc.Ellipsoid.Label='Ellipsoid'

doc.recompute()




cut = doc.addObject("Part::Cut","Cut")
cut.Base = topcase
cut.Tool = ellipse
doc.recompute()

topcase2 =doc.addObject("Part::Feature","topcase2")
topcase2 .Shape=Part.Solid(Part.Shell(cut.Shape.Faces))

doc.removeObject(cut.Label)
doc.removeObject(topcase.Label)
doc.removeObject(ellipse.Label)




ellipse2 = doc.addObject("Part::Ellipsoid","Ellipsoid2")
doc.Ellipsoid2.Radius1=8.00
doc.Ellipsoid2.Radius2=6.00
doc.Ellipsoid2.Radius3=5.00
doc.Ellipsoid2.Angle1=-90.00
doc.Ellipsoid2.Angle2=90.00
doc.Ellipsoid2.Angle3=360.00

doc.Ellipsoid2.Placement=App.Placement(App.Vector(20.00,25.00,3),App.Rotation(0.00,0.00,0.00,1.00))
doc.Ellipsoid2.Label='Ellipsoid2'

doc.recompute()



cut = doc.addObject("Part::Cut","Cut")
cut.Base = FullBase
cut.Tool = ellipse2
doc.recompute()

FullBase2 =doc.addObject("Part::Feature","FullBase2")
FullBase2 .Shape=Part.Solid(Part.Shell(cut.Shape.Faces))

doc.removeObject(cut.Label)
doc.removeObject(FullBase.Label)
doc.removeObject(ellipse2.Label)




#doc.getObject("topcase").Transparency = 50
FreeCADGui.getDocument("Unnamed").getObject("topcase2").Transparency = 40
FreeCADGui.getDocument("Unnamed").getObject("FullBase2").Transparency = 40


#doc.removeObject("topcase") 

#del __s__, __o__
doc.removeObject("TopJoin")
doc.removeObject(sodaqbox1.Label)
doc.removeObject(sealbox.Label)
doc.recompute()
